module ietf-yp-observation {
  yang-version 1.1;
  namespace "urn:ietf:params:xml:ns:yang:ietf-yp-observation";
  prefix ypot;

  import ietf-yang-types {
    prefix yang;
    reference
      "RFC 6991: Common YANG Data Types";
  }
  import ietf-yang-push {
    prefix yp;
    reference
      "RFC 8641: Subscription to YANG Notifications for Datastore Updates";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }

  organization
    "IETF NETCONF (Network Configuration) Working Group";
  contact
    "WG Web:   &lt;http:/tools.ietf.org/wg/netconf/&gt;
     WG List:  &lt;mailto:netconf@ietf.org&gt;

     Authors:  Thomas Graf
               &lt;mailto:thomas.graf@swisscom.com&gt;
               Benoit Claise
               &lt;mailto:benoit.claise@huawei.com&gt;
               Alex Huang Feng
               &lt;mailto:alex.huang-feng@insa-lyon.fr&gt;";
  description
    "Defines YANG-Push event notification header with the observation
     time in streaming update notifications.

     Copyright (c) 2025 IETF Trust and the persons identified as
     authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2025-06-04 {
    description
      "First revision";
    reference
      "RFC XXXX: Extensible YANG Model for Network Telemetry Notifications";
  }

  feature yang-push-observation-timestamp {
    description
      "This feature indicates the YANG-push Notifications support
       the observation timestamps in streaming update notifications.";
  }

  grouping yang-push-observation {
    description
      "This grouping adds the observation timestamp for the observed metrics.";
    leaf timestamp {
      type yang:date-and-time;
      description
        "This is the time when metrics were observed.";
    }
    leaf point-in-time {
      type enumeration {
        enum current-accounting {
          description
            "For periodical subscriptions, the point-in-time
             where the metrics are being polled and observed.";
        }
        enum initial-state {
          description
            "For 'on-change sync on start' subscriptions, the
             initial point in time when the subscription was established
             and the state was observed.";
        }
        enum state-changed {
          description
            "For 'on-change sync on start' subscriptions, the
             point in time when the state change was observed after the
             subscription was established.";
        }
      }
      description
        "This describes at which point in time the metrics were observed";
    }
  }

  // Event notifications
  augment "/yp:push-update" {
    description
      "This augmentation adds the observation timestamp of the accounted
       metrics in the push-update notification.";
    uses ypot:yang-push-observation;
  }

  augment "/yp:push-change-update" {
    description
      "This augmentation adds the observation timestamp of the event
       in the push-change-update notification.";
    uses ypot:yang-push-observation;
  }

  // Event capabilities
  augment "/sysc:system-capabilities"
        + "/notc:subscription-capabilities" {
    description
      "Add YANG-Push notification capabilities to system-level capability
       container.";
    leaf yang-push-observation-supported {
      if-feature "yang-push-observation-timestamp";
      type boolean;
      description
        "Specifies whether the publisher supports exporting
         observation-timestamp and point-in-time in notifications.";
      reference
        "RFC XXXX: Extensible YANG Model for YANG-Push Notifications";
    }
  }
}
